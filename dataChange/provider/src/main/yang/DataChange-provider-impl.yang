module DataChange-provider-impl {

    yang-version 1;
    namespace "org:onap:ccsdk:sli:northbound:datachange:provider:impl";
    prefix "DataChange-provider-impl";

    import config { prefix config; revision-date 2013-04-05; }
    import opendaylight-md-sal-binding { prefix mdsal; revision-date 2013-10-28; }
    import opendaylight-sal-binding-broker-impl {
        prefix binding-impl;
        revision-date 2013-10-28;
    }

     description
        "This module contains the base YANG definitions for
        DataChange-provider impl implementation.";

    revision "2014-05-23" {
        description
            "Initial revision.";
    }

    // This is the definition of the service implementation as a module identity.
    identity DataChange-provider-impl {
            base config:module-type;

            // Specifies the prefix for generated java classes.
            config:java-name-prefix DataChangeProvider;
    }

    // Augments the 'configuration' choice node under modules/module.
    // We consume the three main services, RPCs, DataStore, and Notifications
    augment "/config:modules/config:module/config:configuration" {
        case DataChange-provider-impl {
            when "/config:modules/config:module/config:type = 'DataChange-provider-impl'";

            container rpc-registry {
                uses config:service-ref {
                    refine type {
                        mandatory true;
                        config:required-identity mdsal:binding-rpc-registry;
                    }
                }
            }

            container notification-publish-adapter {
                uses config:service-ref {
                    refine type {
                        mandatory true;
                        config:required-identity binding-impl:binding-new-notification-publish-service;
                    }
                }
            }

            container data-broker {
                uses config:service-ref {
                    refine type {
                        mandatory false;
                        config:required-identity mdsal:binding-async-data-broker;
                    }
                }
            }
        }
    }
}
